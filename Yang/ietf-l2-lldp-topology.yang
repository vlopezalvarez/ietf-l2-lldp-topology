module ietf-l2-lldp-topology {
  yang-version 1.1;
  namespace
    "urn:ietf:params:xml:ns:yang:ietf-l2-lldp-topology";
  prefix "lldp";

  import ietf-network {
       prefix nw;
       reference
         "RFC 8345: A YANG Data Model for Network Topologies";
  }
  import ietf-network-topology {
       prefix nt;
       reference
         "RFC 8345: A YANG Data Model for Network Topologies";
  }
  import ietf-yang-types {
       prefix yang;
       reference
         "Section 3 of RFC 6991";
  }
  import ietf-l2-topology {
    prefix "l2t";
  }
  organization
    "IETF OPSA (Operations and Management Area) Working Group";
  contact
    "Editor:    Oscar Gonzalez de Dios
                 <mailto:oscar.gonzalezdedios@telefonica.com>
    Editor:   Samier Barguil
                 <mailto:samier.barguilgiraldo.ext@telefonica.com>
    Editor:   Victor Lopez
                 <mailto:victor.lopez@nokia.com>";
  description
    "This module defines a model for Layer 2 LLDP
     topologies.

     Copyright (c) 2018 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).

     This version of this YANG module is part of
     RFC 8346; see the RFC itself for full legal notices.";

  revision "2020-03-11" {
    description
      "Initial revision.";
    reference
      "draft-ietf-i2rs-yang-l2-network-topology-13: A YANG Data Model for Layer 2 Topologies";
  }

  grouping lldp-topology-type {
    description "Identifies the topology type to be lldp.";
    container lldp-topology {
      presence "indicates lldp topology";
      description
        "The presence of the container node indicates lldp
        topology";
    }
  }


grouping lldp-termination-point-attributes {
    description "LLDP termination point scope attributes";
    container lldp-termination-point-attributes {
      description "";
    leaf enable {
        type boolean;
        default "false";
        description
          "lldp state on/off";
      }

    leaf neighbor {
        type yang:mac-address;
        config false;
        description
          "Neighbor Mac Address";
      } 
    leaf age {
      type uint64;
      config false; 
      units "seconds";
      description
        "Age since discovery";
    }
    leaf ttl {
     type uint16;
     units "seconds";
     description
        "The time-to-live (TTL) is a mandatory TLV which indicates
        how long information from the neighbor should be considered
        valid.";
    }
    container lldp-tlvs-state{
    config false; 
    description "";

    leaf sys-name {
      type string;
      config false;
      description
        "The SYSTEM NAME is a TLV which identifies the
        device";
    }

    leaf sys-desc {
      type string;
      config false;
      description
        "The SYSTEM DESCRIPTION is a  TLV which identifies 
        the system";
    }

    leaf port-id {
      type string;
      config false;
      description
        "The Port ID is a mandatory TLV which identifies the port
        component of the endpoint identifier associated with the
        transmitting LLDP agent. If the specified port is an IEEE
        802.3 Repeater port, then this TLV is optional.";
    }
    leaf port-description {
      type string;
      config false;
      description
        "The binary string containing the actual port identifier for
        the port which this LLDP PDU was transmitted. The source and
        format of this field is defined by PtopoPortId from
        RFC2922.";
          }

        }
      }
    }

  augment "/nw:networks/nw:network/nw:network-types" {
       description
         "Introduces new network type for L2 topology.";
       uses lldp-topology-type;
  }
    
  augment "/nw:networks/nw:network/nw:node/nt:termination-point/l2t:l2-termination-point-attributes" {
       when '/nw:networks/nw:network/nw:network-types/lldp:lldp-topology' {
         description
           "Augmentation parameters apply only for networks
            with L2 topology.";
       }
       description
         "Augments L2 topology termination point information.";
       uses lldp-termination-point-attributes;
     } 

}
